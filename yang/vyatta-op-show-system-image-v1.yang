module vyatta-op-show-system-image-v1 {
	namespace "urn:vyatta.com:mgmt:vyatta-op-show-system-image:1";
	prefix vyatta-op-show-system-image-v1;

	import vyatta-opd-extensions-v1 {
		prefix opd;
	}
	import vyatta-op-show-v1 {
		prefix show;
	}
	import vyatta-op-show-system-v1 {
		prefix system;
	}

	organization "AT&T Inc.";
	contact
		"AT&T
		 Postal: 208 S. Akard Street
				 Dallas, TX 25202
		 Web: www.att.com";

	description
		"Copyright (c) 2019, AT&T Intellectual Property.
		 All rights reserved.

		Redistribution and use in source and binary forms, with or without
		modification, are permitted provided that the following conditions
		are met:

		  1. Redistributions of source code must retain the above copyright
		     notice, this list of conditions and the following disclaimer.
		  2. Redistributions in binary form must reproduce the above
		     copyright notice, this list of conditions and the following
		     disclaimer in the documentation and/or other materials provided
		     with the distribution.
		  3. Neither the name of the copyright holder nor the names of its
		     contributors may be used to endorse or promote products derived
		     from this software without specific prior written permission.

		THIS SOFTWARE IS PROVIDED BY THE COPYRIGHT HOLDERS AND CONTRIBUTORS
		'AS IS' AND ANY EXPRESS OR IMPLIED WARRANTIES, INCLUDING, BUT NOT
		LIMITED TO, THE IMPLIED WARRANTIES OF MERCHANTABILITY AND FITNESS
		FOR A PARTICULAR PURPOSE ARE DISCLAIMED. IN NO EVENT SHALL THE
		COPYRIGHT HOLDER OR CONTRIBUTORS BE LIABLE FOR ANY DIRECT, INDIRECT,
		INCIDENTAL, SPECIAL, EXEMPLARY, OR CONSEQUENTIAL DAMAGES (INCLUDING,
		BUT NOT LIMITED TO, PROCUREMENT OF SUBSTITUTE GOODS OR SERVICES;
		LOSS OF USE, DATA, OR PROFITS; OR BUSINESS INTERRUPTION) HOWEVER
		CAUSED AND ON ANY THEORY OF LIABILITY, WHETHER IN CONTRACT, STRICT
		LIABILITY, OR TORT (INCLUDING NEGLIGENCE OR OTHERWISE) ARISING IN
		ANY WAY OUT OF THE USE OF THIS SOFTWARE, EVEN IF ADVISED OF THE
		POSSIBILITY OF SUCH DAMAGE.

		SPDX-License-Identifier: BSD-3-Clause

		Defines the top level 'image' level under 'show system' for operational CLI";

	revision 2019-12-18 {
		description "Adds packages node to print all installed packaged
			in a given image.";
	}
	revision 2019-02-15 {
		description "Initial version";
	}

	opd:augment /show:show/system:system {
		opd:command image {
			opd:help "Show installed Vyatta images";
			opd:on-enter "vyatta-image-op --action=show-images";

			opd:command storage {
				opd:help "Show disk space utilization of system-image images";
				opd:on-enter 'vyatta-image-op --action=show-storage';
			}
			opd:command version {
				opd:help "Show installed Vyatta images with Vyatta version number";
				opd:on-enter 'vyatta-image-op --action=show-versions';
			}
			opd:argument image {
				opd:help "Name of an installed image";
				opd:allowed 'vyatta-image-op --action=list-images';
				opd:privileged true;
				type string;
			
				opd:command packages {
					opd:help "Print installed packages of selected image";
					opd:on-enter 'vyatta-squashfs-chroot "$4" LIST';
					opd:privileged true;
				}
			}
		}
	}
}
