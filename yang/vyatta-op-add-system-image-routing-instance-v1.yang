module vyatta-op-add-system-image-routing-instance-v1 {
	namespace "urn:vyatta.com:mgmt:vyatta-op-add-system-image-routing-instance:1";
	prefix vyatta-op-add-system-image-routing-instance-v1;

	import vyatta-opd-extensions-v1 {
		prefix opd;
	}
	import vyatta-op-add-v1 {
		prefix add;
	}
	import vyatta-op-add-system-v1 {
		prefix system;
	}
	import vyatta-op-add-system-image-v1 {
		prefix image;
	}

	organization "AT&T Inc.";
	contact
		"AT&T
		 Postal: 208 S. Akard Street
				 Dallas, TX 75202
		 Web: www.att.com";

	description
		"Copyright (c) 2020-2021, AT&T Intellectual Property.
		 All rights reserved.

		Redistribution and use in source and binary forms, with or without
		modification, are permitted provided that the following conditions
		are met:

		  1. Redistributions of source code must retain the above copyright
		     notice, this list of conditions and the following disclaimer.
		  2. Redistributions in binary form must reproduce the above
		     copyright notice, this list of conditions and the following
		     disclaimer in the documentation and/or other materials provided
		     with the distribution.
		  3. Neither the name of the copyright holder nor the names of its
		     contributors may be used to endorse or promote products derived
		     from this software without specific prior written permission.

		THIS SOFTWARE IS PROVIDED BY THE COPYRIGHT HOLDERS AND CONTRIBUTORS
		'AS IS' AND ANY EXPRESS OR IMPLIED WARRANTIES, INCLUDING, BUT NOT
		LIMITED TO, THE IMPLIED WARRANTIES OF MERCHANTABILITY AND FITNESS
		FOR A PARTICULAR PURPOSE ARE DISCLAIMED. IN NO EVENT SHALL THE
		COPYRIGHT HOLDER OR CONTRIBUTORS BE LIABLE FOR ANY DIRECT, INDIRECT,
		INCIDENTAL, SPECIAL, EXEMPLARY, OR CONSEQUENTIAL DAMAGES (INCLUDING,
		BUT NOT LIMITED TO, PROCUREMENT OF SUBSTITUTE GOODS OR SERVICES;
		LOSS OF USE, DATA, OR PROFITS; OR BUSINESS INTERRUPTION) HOWEVER
		CAUSED AND ON ANY THEORY OF LIABILITY, WHETHER IN CONTRACT, STRICT
		LIABILITY, OR TORT (INCLUDING NEGLIGENCE OR OTHERWISE) ARISING IN
		ANY WAY OUT OF THE USE OF THIS SOFTWARE, EVEN IF ADVISED OF THE
		POSSIBILITY OF SUCH DAMAGE.

		SPDX-License-Identifier: BSD-3-Clause

		Defines the 'routing instance' level under 'add system image' for operational CLI";

	revision 2021-08-24 {
		description "Use environment variables to pass credentials";
	}
	revision 2021-03-31 {
		description "Allow user to install images without setting image as the default boot.";
	}
	revision 2021-02-10 {
		description "Add username/password options to match non-routing-instance command.
			Obsolete the user-id/passphrase options.";
	}
	revision 2020-09-15 {
		description "Initial version";
	}

	opd:augment /add:add/system:system/image:image {

		opd:option routing-instance {
			opd:help "Routing instance for retrieving the iso";
			opd:allowed 'getvrflist --name-only';
			type string;

			opd:argument image-url {
				opd:help "URL of system image file to be installed";
				opd:on-enter 'chvrf "${5}" vyatta-install-image "${6}"';
				opd:privileged true;
				type string {
						opd:pattern-help '<http|https|ftp|tftp|scp url>';
						pattern '(http|https|ftp|tftp|scp)://.*/.*' {
							error-message "URL scheme must one of http, https, ftp, tftp, scp";
						}
					}

				opd:command defer-boot {
					opd:help "Do not use the new image as the default boot";
					opd:on-enter 'vyatta-install-image --defer-boot "${6}"';
					opd:privileged true;

					opd:option username {
						opd:help "Username for authentication";
						type string;

						opd:option password {
							opd:help "Password to use with authentication";
							opd:on-enter 'export VY_ADD_IMG_USER="${9}" VY_ADD_IMG_PASS="${11}" && \
								chvrf "${5}" vyatta-install-image --defer-boot "${6}"';
							opd:privileged true;
							opd:secret true;
							type string;
						}
					}
				}


				opd:option username {
					opd:help "Username for authentication";
					type string;

					opd:option password {
						opd:help "Password to use with authentication";
						opd:on-enter 'export VY_ADD_IMG_USER="${8}" VY_ADD_IMG_PASS="${10}" && \
							chvrf "${5}" vyatta-install-image "${6}"';
						opd:privileged true;
						opd:secret true;
						type string;
					}
				}

				opd:option user-id {
					status obsolete;
					opd:help "Username for authentication";
					type string;

					opd:option passphrase {
						opd:help "Password to use with authentication";
						opd:on-enter 'export VY_ADD_IMG_USER="${8}" VY_ADD_IMG_PASS="${10}" && \
							chvrf "${5}" vyatta-install-image "${6}"';
						opd:privileged true;
						opd:secret true;
						type string;
					}
				}
			}
		}
	}
}
