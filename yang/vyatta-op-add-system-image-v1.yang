module vyatta-op-add-system-image-v1 {
	namespace "urn:vyatta.com:mgmt:vyatta-op-add-system-image:1";
	prefix vyatta-op-add-system-image-v1;

	import vyatta-opd-extensions-v1 {
		prefix opd;
	}
	import vyatta-op-add-v1 {
		prefix add;
	}
	import vyatta-op-add-system-v1 {
		prefix system;
	}

	organization "AT&T Inc.";
	contact
		"AT&T
		 Postal: 208 S. Akard Street
				 Dallas, TX 75202
		 Web: www.att.com";

	description
		"Copyright (c) 2019, 2021 AT&T Intellectual Property.
		 All rights reserved.

		Redistribution and use in source and binary forms, with or without
		modification, are permitted provided that the following conditions
		are met:

		  1. Redistributions of source code must retain the above copyright
		     notice, this list of conditions and the following disclaimer.
		  2. Redistributions in binary form must reproduce the above
		     copyright notice, this list of conditions and the following
		     disclaimer in the documentation and/or other materials provided
		     with the distribution.
		  3. Neither the name of the copyright holder nor the names of its
		     contributors may be used to endorse or promote products derived
		     from this software without specific prior written permission.

		THIS SOFTWARE IS PROVIDED BY THE COPYRIGHT HOLDERS AND CONTRIBUTORS
		'AS IS' AND ANY EXPRESS OR IMPLIED WARRANTIES, INCLUDING, BUT NOT
		LIMITED TO, THE IMPLIED WARRANTIES OF MERCHANTABILITY AND FITNESS
		FOR A PARTICULAR PURPOSE ARE DISCLAIMED. IN NO EVENT SHALL THE
		COPYRIGHT HOLDER OR CONTRIBUTORS BE LIABLE FOR ANY DIRECT, INDIRECT,
		INCIDENTAL, SPECIAL, EXEMPLARY, OR CONSEQUENTIAL DAMAGES (INCLUDING,
		BUT NOT LIMITED TO, PROCUREMENT OF SUBSTITUTE GOODS OR SERVICES;
		LOSS OF USE, DATA, OR PROFITS; OR BUSINESS INTERRUPTION) HOWEVER
		CAUSED AND ON ANY THEORY OF LIABILITY, WHETHER IN CONTRACT, STRICT
		LIABILITY, OR TORT (INCLUDING NEGLIGENCE OR OTHERWISE) ARISING IN
		ANY WAY OUT OF THE USE OF THIS SOFTWARE, EVEN IF ADVISED OF THE
		POSSIBILITY OF SUCH DAMAGE.

		SPDX-License-Identifier: BSD-3-Clause

		Defines the top level 'image' level under 'add system' for operational CLI";

	revision 2021-08-24 {
		description "Use environment variables to pass credentials";
	}
	revision 2021-03-31 {
		description "Allow user to install images without setting image as the default boot.";
	}
	revision 2019-12-16 {
		description "Adding ability to install specific packages to a target image via the
			packages option.";
	}
	revision 2019-02-15 {
		description "Initial version";
	}

	opd:augment /add:add/system:system {
		opd:command image {
			opd:help "Add a new image to the system";

			opd:argument image-url {
				opd:help "File name or URL of system image file to be installed";
				opd:allowed 'echo -e "<ISO_URL>\n<ISO_file>" && vyatta-image-op --action=list-images';
				opd:on-enter 'vyatta-install-image "$4"';
				opd:privileged true;
				type string;

				opd:command username {
					opd:help "Username for authentication";

					opd:argument user-id {
						opd:help "Username for authentication";
						type string;

						opd:command password {
							opd:help "Password to use with authentication";

							opd:argument passphrase {
								opd:help "Password to use with authentication";
								opd:on-enter 'export VY_ADD_IMG_USER="$6" VY_ADD_IMG_PASS="$8" && \
									vyatta-install-image "$4"';
								opd:privileged true;
								opd:secret true;
								type string;
							}
						}
					}
				}
				opd:command defer-boot {
					opd:help "Do not use the new image as the default boot";
					opd:on-enter 'vyatta-install-image --defer-boot "$4"';
					opd:privileged true;

					opd:command username {
						opd:help "Username for authentication";

						opd:argument user-id {
							opd:help "Username for authentication";
							type string;

							opd:command password {
								opd:help "Password to use with authentication";

								opd:argument passphrase {
									opd:help "Password to use with authentication";
									opd:on-enter 'export VY_ADD_IMG_USER="$7" VY_ADD_IMG_PASS="$9" && \
										vyatta-install-image --defer-boot "$4"';
									opd:privileged true;
									opd:secret true;
									type string;
								}
							}
						}
					}
				}
				opd:command packages {
					opd:help "Install selected list of packages";
					opd:repeatable true;
					opd:inherit "" {
						opd:on-enter 'vyatta-hotfix "$4" "${@:5}"';
						opd:privileged true;
					}

					opd:argument package-list {
						opd:help "Space separated list of packages";
						type string;
					}
				}
				opd:argument auto-install {
					opd:help "Trigger auto-install";
					opd:allowed 'echo -en ".\n.."';
					opd:on-enter 'vyatta-image-op --action=vyatta-autoinstall "$4" "$5"';
					opd:privileged true;
					type string;
				}
			}
		}
	}
}
